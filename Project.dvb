Attribute VB_Name = "formLine"
Attribute VB_Base = "0{6349C2CC-D36B-48B3-B7CB-E4B96DCC64A9}{A16E7AF6-1D77-4C96-8F84-60611BBF82C9}"
Attribute VB_GlobalNameSpace = False
Attribute VB_Creatable = False
Attribute VB_PredeclaredId = True
Attribute VB_Exposed = False
Attribute VB_TemplateDerived = False
Attribute VB_Customizable = False
Private Sub CommandButton1_Click()
    Dim s(0 To 2) As Double
    Dim e(0 To 2) As Double
    s(0) = TextBox1
    s(1) = TextBox2
    s(2) = TextBox3
    e(0) = TextBox4
    e(1) = TextBox5
    e(2) = TextBox6
    With ThisDrawing.ModelSpace
        .AddLine s, e
        .Item(.Count - 1).Update
    End With
End Sub
