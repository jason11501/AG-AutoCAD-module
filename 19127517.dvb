Attribute VB_Name = "formLine"
Attribute VB_Base = "0{EB420627-865A-4DA3-9AC5-2D2E94733985}{401E06F9-08C3-4949-BBAA-35F24202E1D0}"
Attribute VB_GlobalNameSpace = False
Attribute VB_Creatable = False
Attribute VB_PredeclaredId = True
Attribute VB_Exposed = False
Attribute VB_TemplateDerived = False
Attribute VB_Customizable = False
Private Sub CommandButton1_Click()
    'Ve duong thang
    Dim a(0 To 2) As Double
    Dim b(0 To 2) As Double
    a(0) = TextBox1
    a(1) = TextBox2
    b(0) = TextBox4
    b(1) = TextBox5
    With ThisDrawing.ModelSpace
        .AddLine a, b
        .Item(.Count - 1).Update
    End With
    ZoomAll
End Sub
